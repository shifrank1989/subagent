-- *****************************************************************
-- China Software CDS2000 Appliance MIB
--
-- DO NOT EDIT THIS FILE MANUALLY. IT IS AUTOMATICALLY GENERATED BY
-- CSS MIB GENERATOR.
--
-- July, 2018 Qiaoshi
--
-- Copyright (c) 2018 by CSS, Inc.
--
-- All rights reserved.
--
-- *****************************************************************
--
-- Top-level infrastructure of the China Software CDS2000 Appliance enterprise MIB tree.
--
-- CDS2000-MIB.my
CDS2000-MIB DEFINITIONS ::= BEGIN

IMPORTS/
OBJECT-GROUP, MODULE-COMPLIANCE, NOTIFICATION-GROUP
FROM SNMPv2-CONF
enterprises, Integer32, Unsigned32, OBJECT-TYPE, MODULE-IDENTITY,
NOTIFICATION-TYPE
FROM SNMPv2-SMI
DisplayString
FROM SNMPv2-TC;

-- July 31, 2018 at 14:50 GMT
-- 1.3.6.1.4.1.66018
CDS2000 MODULE-IDENTITY
LAST-UPDATED "201807311450Z"        -- July 31, 2018 at 14:50 GMT
ORGANIZATION
""
CONTACT-INFO
""
DESCRIPTION
"CDS2000's MIB."
::= { enterprises 66018 }

--  Node definitions
-- This part will include all details about the CDS2000.
-- 1.3.6.1.4.1.66018.1
SYSINFO OBJECT IDENTIFIER ::= { CDS2000 1 }


-- 1.3.6.1.4.1.66018.1.1
GetCpuNum OBJECT-TYPE
SYNTAX DisplayString (SIZE (0..100))
MAX-ACCESS read-only
STATUS current
DESCRIPTION
"Example : 01"
::= { Cpu 1 }
END

-- CDS2000-MIB.my
